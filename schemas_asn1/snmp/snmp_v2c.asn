SNMPv2-SMI DEFINITIONS ::= BEGIN

ObjectName ::= OBJECT IDENTIFIER

NotificationName ::= OBJECT IDENTIFIER

ObjectSyntax ::= CHOICE {
    simple            SimpleSyntax,
    application-wide  ApplicationSyntax
    -- TODO: SEQUENCE
}

SimpleSyntax ::= CHOICE {
    integer-value   INTEGER (-2147483648..2147483647),
    string-value    OCTET STRING (SIZE (0..65535)),
    objectID-value  OBJECT IDENTIFIER
}

Integer32 ::= [UNIVERSAL 2] IMPLICIT INTEGER (-2147483648..2147483647)

ApplicationSyntax ::= CHOICE {
    ipAddress-value         IpAddress,
    counter-value           Counter32,
    timeticks-value         TimeTicks,
    arbitrary-value         Opaque,
    big-counter-value       Counter64,
    unsigned-integer-value  Unsigned32
}

IpAddress ::= [APPLICATION 0] IMPLICIT OCTET STRING (SIZE (4))

Counter32 ::= [APPLICATION 1] IMPLICIT INTEGER (0..4294967295)

Gauge32 ::= [APPLICATION 2] IMPLICIT INTEGER (0..4294967295)

Unsigned32 ::= [APPLICATION 2] IMPLICIT INTEGER (0..4294967295)

TimeTicks ::= [APPLICATION 3] IMPLICIT INTEGER (0..4294967295)

Opaque ::= [APPLICATION 4] IMPLICIT OCTET STRING

Counter64 ::= [APPLICATION 6] IMPLICIT INTEGER (0..18446744073709551615)

END


SNMPv2-PDU DEFINITIONS ::= BEGIN

IMPORTS
    ObjectName, ObjectSyntax, Integer32
    FROM SNMPv2-SMI;

PDUs ::= CHOICE {
    get-request       GetRequest-PDU,
    get-next-request  GetNextRequest-PDU,
    get-bulk-request  GetBulkRequest-PDU,
    response          Response-PDU,
    set-request       SetRequest-PDU,
    inform-request    InformRequest-PDU,
    snmpV2-trap       SNMPv2-Trap-PDU,
    report            Report-PDU
}

GetRequest-PDU ::= [0] IMPLICIT PDU

GetNextRequest-PDU ::= [1] IMPLICIT PDU

Response-PDU ::= [2] IMPLICIT PDU

SetRequest-PDU ::= [3] IMPLICIT PDU

GetBulkRequest-PDU ::= [5] IMPLICIT BulkPDU

InformRequest-PDU ::= [6] IMPLICIT PDU

SNMPv2-Trap-PDU ::= [7] IMPLICIT PDU

Report-PDU ::= [8] IMPLICIT PDU

PDU ::= SEQUENCE {
    request-id         Integer32,
    error-status       INTEGER { noError(0),
                                 tooBig(1),
                                 noSuchName(2),
                                 badValue(3),
                                 readOnly(4),
                                 genErr(5),
                                 noAccess(6),
                                 wrongType(7),
                                 wrongLength(8),
                                 wrongEncoding(9),
                                 wrongValue(10),
                                 noCreation(11),
                                 inconsistentValue(12),
                                 resourceUnavailable(13),
                                 commitFailed(14),
                                 undoFailed(15),
                                 authorizationError(16),
                                 notWritable(17),
                                 inconsistentName(18) },
    error-index        INTEGER (0..2147483647),
    variable-bindings  VarBindList
}

BulkPDU ::= SEQUENCE {
    request-id       Integer32,
    non-repeaters    INTEGER (0..2147483647),
    max-repetitions  INTEGER (0..2147483647),
    variable-bindings   VarBindList
}

VarBind ::= SEQUENCE {
    name  ObjectName,
    data  CHOICE {
        value           ObjectSyntax,
        unSpecified     NULL,
        noSuchObject    [0] IMPLICIT NULL,
        noSuchInstance  [1] IMPLICIT NULL,
        endOfMibView    [2] IMPLICIT NULL
    }
}

VarBindList ::= SEQUENCE (SIZE (0..2147483647)) OF VarBind

END


COMMUNITY-BASED-SNMPv2 DEFINITIONS ::= BEGIN

IMPORTS
    PDUs
    FROM SNMPv2-PDU;

Message ::= SEQUENCE {
    version    INTEGER { version-2(1) },
    community  OCTET STRING,
    data       PDUs
}

END
